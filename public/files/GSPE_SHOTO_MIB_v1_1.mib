BATTERY-MANAGEMENT-MIB DEFINITIONS ::= BEGIN

IMPORTS
    MODULE-IDENTITY, OBJECT-TYPE, NOTIFICATION-TYPE,
    Integer32, Unsigned32, Counter32, Gauge32, TimeTicks
        FROM SNMPv2-SMI
    DisplayString, TruthValue
        FROM SNMPv2-TC
    MODULE-COMPLIANCE, OBJECT-GROUP, NOTIFICATION-GROUP
        FROM SNMPv2-CONF;

PT-GSPE MODULE-IDENTITY
    LAST-UPDATED "202501040000Z"
    ORGANIZATION "BMS Battery Management System"
    CONTACT-INFO 
        "Contact: BMS Support Team
         Email: support@bms.local
         Description: Battery Management System SNMP MIB"
    DESCRIPTION
        "This MIB module defines objects for monitoring and managing
         battery systems including Shoto SDA10-48100 lithium batteries
         and battery chargers through SNMP protocol."
    REVISION "202501040000Z"
    DESCRIPTION "Revised version with payload-matching naming convention"
    ::= { enterprises 10000 }

-- Enterprise and organizational structure
ShotoBattery     OBJECT IDENTIFIER ::= { PT-GSPE 11 }
Config           OBJECT IDENTIFIER ::= { ShotoBattery 5 }
Equipment        OBJECT IDENTIFIER ::= { ShotoBattery 12 }
Traps            OBJECT IDENTIFIER ::= { ShotoBattery 13 }
TrapProtect      OBJECT IDENTIFIER ::= { ShotoBattery 14 }
TrapStatus       OBJECT IDENTIFIER ::= { ShotoBattery 15 }

-- Configuration Objects (5.x.0)
ConfigGroup  OBJECT IDENTIFIER ::= { Config 1 }

snmpIPAddress OBJECT-TYPE
    SYNTAX      DisplayString (SIZE(7..15))
    MAX-ACCESS  read-write
    STATUS      current
    DESCRIPTION "SNMP agent IP address configuration"
    ::= { Config 10 }

snmpNetmask OBJECT-TYPE
    SYNTAX      DisplayString (SIZE(7..15))
    MAX-ACCESS  read-write
    STATUS      current
    DESCRIPTION "SNMP agent network mask"
    ::= { Config 20 }

snmpGateway OBJECT-TYPE
    SYNTAX      DisplayString (SIZE(7..15))
    MAX-ACCESS  read-write
    STATUS      current
    DESCRIPTION "SNMP agent gateway address"
    ::= { Config 30 }

snmpVersion OBJECT-TYPE
    SYNTAX      DisplayString (SIZE(1..3))
    MAX-ACCESS  read-write
    STATUS      current
    DESCRIPTION "SNMP protocol version (1, 2c, 3)"
    ::= { Config 40 }

snmpCommunity OBJECT-TYPE
    SYNTAX      DisplayString (SIZE(1..32))
    MAX-ACCESS  read-write
    STATUS      current
    DESCRIPTION "SNMP community string"
    ::= { Config 50 }

snmpPort OBJECT-TYPE
    SYNTAX      DisplayString (SIZE(1..5))
    MAX-ACCESS  read-write
    STATUS      current
    DESCRIPTION "SNMP agent listening port"
    ::= { Config 60 }

systemOID OBJECT-TYPE
    SYNTAX      DisplayString (SIZE(1..64))
    MAX-ACCESS  read-write
    STATUS      current
    DESCRIPTION "System object identifier"
    ::= { Config 70 }

snmpSecurityName OBJECT-TYPE
    SYNTAX      DisplayString (SIZE(1..32))
    MAX-ACCESS  read-write
    STATUS      current
    DESCRIPTION "SNMPv3 security name"
    ::= { Config 80 }

snmpAuthKey OBJECT-TYPE
    SYNTAX      DisplayString (SIZE(1..32))
    MAX-ACCESS  read-write
    STATUS      current
    DESCRIPTION "SNMPv3 authentication key"
    ::= { Config 90 }

snmpPrivKey OBJECT-TYPE
    SYNTAX      DisplayString (SIZE(1..32))
    MAX-ACCESS  read-write
    STATUS      current
    DESCRIPTION "SNMPv3 privacy key"
    ::= { Config 100 }

snmpSecurityLevel OBJECT-TYPE
    SYNTAX      DisplayString (SIZE(1..16))
    MAX-ACCESS  read-write
    STATUS      current
    DESCRIPTION "SNMPv3 security level"
    ::= { Config 110 }

deviceName OBJECT-TYPE
    SYNTAX      DisplayString (SIZE(1..64))
    MAX-ACCESS  read-write
    STATUS      current
    DESCRIPTION "Device name identifier"
    ::= { Config 120 }

siteName OBJECT-TYPE
    SYNTAX      DisplayString (SIZE(1..64))
    MAX-ACCESS  read-write
    STATUS      current
    DESCRIPTION "Installation site name"
    ::= { Config 130 }

-- Equipment Objects - Battery Data (matches MQTT payload naming)
batteryData    OBJECT IDENTIFIER ::= { Equipment 1 }

-- Battery Main Parameters (1-14) - Naming matches payload keys
packVoltage OBJECT-TYPE
    SYNTAX      Integer32
    UNITS       "centi-volts"
    MAX-ACCESS  read-only
    STATUS      current
    DESCRIPTION "Pack Voltage - Battery pack voltage in centi-volts (divide by 100 for actual volts)
                 MQTT Payload Key: 'Pack Voltage'"
    ::= { batteryData 1 }

current OBJECT-TYPE
    SYNTAX      Integer32
    UNITS       "centi-amperes"
    MAX-ACCESS  read-only
    STATUS      current
    DESCRIPTION "Current - Battery current in centi-amperes (divide by 100 for actual amperes)
                 MQTT Payload Key: 'Current'"
    ::= { batteryData 2 }

remainingCapacity OBJECT-TYPE
    SYNTAX      Integer32
    UNITS       "centi-ampere-hours"
    MAX-ACCESS  read-only
    STATUS      current
    DESCRIPTION "Remaining capacity - Remaining capacity in centi-ampere-hours
                 MQTT Payload Key: 'Remaining capacity'"
    ::= { batteryData 3 }

totalCapacity OBJECT-TYPE
    SYNTAX      Integer32
    UNITS       "centi-ampere-hours"
    MAX-ACCESS  read-only
    STATUS      current
    DESCRIPTION "Total Capacity - Total capacity in centi-ampere-hours
                 MQTT Payload Key: 'Total Capacity'"
    ::= { batteryData 4 }

totalDischargeCapacity OBJECT-TYPE
    SYNTAX      Integer32
    UNITS       "ampere-hours"
    MAX-ACCESS  read-only
    STATUS      current
    DESCRIPTION "Total Discharge Capacity - Total discharge capacity in ampere-hours
                 MQTT Payload Key: 'Total Discharge Capacity'"
    ::= { batteryData 5 }

soc OBJECT-TYPE
    SYNTAX      Integer32
    UNITS       "deci-percent"
    MAX-ACCESS  read-only
    STATUS      current
    DESCRIPTION "SOC - State of Charge in deci-percent (divide by 10 for actual percentage)
                 MQTT Payload Key: 'SOC'"
    ::= { batteryData 6 }

soh OBJECT-TYPE
    SYNTAX      Integer32
    UNITS       "deci-percent"
    MAX-ACCESS  read-only
    STATUS      current
    DESCRIPTION "SOH - State of Health in deci-percent (divide by 10 for actual percentage)
                 MQTT Payload Key: 'SOH'"
    ::= { batteryData 7 }

cycle OBJECT-TYPE
    SYNTAX      Integer32
    MAX-ACCESS  read-only
    STATUS      current
    DESCRIPTION "Cycle - Battery cycle count
                 MQTT Payload Key: 'Cycle'"
    ::= { batteryData 8 }

averagOfCellVotage OBJECT-TYPE
    SYNTAX      Integer32
    UNITS       "milli-volts"
    MAX-ACCESS  read-only
    STATUS      current
    DESCRIPTION "Averag of Cell Votage - Average cell voltage in milli-volts (divide by 1000 for volts)
                 MQTT Payload Key: 'Averag of Cell Votage' (note: typo in original)"
    ::= { batteryData 9 }

maxCellVoltage OBJECT-TYPE
    SYNTAX      Integer32
    UNITS       "milli-volts"
    MAX-ACCESS  read-only
    STATUS      current
    DESCRIPTION "Max Cell Voltage - Maximum cell voltage in milli-volts
                 MQTT Payload Key: 'Max Cell Voltage'"
    ::= { batteryData 10 }

minCellVoltage OBJECT-TYPE
    SYNTAX      Integer32
    UNITS       "milli-volts"
    MAX-ACCESS  read-only
    STATUS      current
    DESCRIPTION "Min Cell Voltage - Minimum cell voltage in milli-volts
                 MQTT Payload Key: 'Min Cell Voltage'"
    ::= { batteryData 11 }

averagOfCellTemperature OBJECT-TYPE
    SYNTAX      Integer32
    UNITS       "centi-celsius"
    MAX-ACCESS  read-only
    STATUS      current
    DESCRIPTION "Averag of Cell Temperature - Average cell temperature in centi-celsius (divide by 100 for degrees C)
                 MQTT Payload Key: 'Averag of Cell Temperature'"
    ::= { batteryData 12 }

maxCellTemperature OBJECT-TYPE
    SYNTAX      Integer32
    UNITS       "centi-celsius"
    MAX-ACCESS  read-only
    STATUS      current
    DESCRIPTION "Max Cell Temperature - Maximum cell temperature in centi-celsius
                 MQTT Payload Key: 'Max Cell Temperature'"
    ::= { batteryData 13 }

minCellTemperature OBJECT-TYPE
    SYNTAX      Integer32
    UNITS       "centi-celsius"
    MAX-ACCESS  read-only
    STATUS      current
    DESCRIPTION "Min Cell Temperature - Minimum cell temperature in centi-celsius
                 MQTT Payload Key: 'Min Cell Temperature'"
    ::= { batteryData 14 }

-- Individual Cell Voltages (15-29)
cell1Voltage OBJECT-TYPE
    SYNTAX      Integer32
    UNITS       "milli-volts"
    MAX-ACCESS  read-only
    STATUS      current
    DESCRIPTION "Cell1 Voltage - Cell 1 voltage in milli-volts
                 MQTT Payload Key: 'Cell1 Voltage'"
    ::= { batteryData 15 }

cell2Voltage OBJECT-TYPE
    SYNTAX      Integer32
    UNITS       "milli-volts"
    MAX-ACCESS  read-only
    STATUS      current
    DESCRIPTION "Cell2 Voltage - Cell 2 voltage in milli-volts
                 MQTT Payload Key: 'Cell2 Voltage'"
    ::= { batteryData 16 }

cell3Voltage OBJECT-TYPE
    SYNTAX      Integer32
    UNITS       "milli-volts"
    MAX-ACCESS  read-only
    STATUS      current
    DESCRIPTION "Cell3 Voltage - Cell 3 voltage in milli-volts
                 MQTT Payload Key: 'Cell3 Voltage'"
    ::= { batteryData 17 }

cell4Voltage OBJECT-TYPE
    SYNTAX      Integer32
    UNITS       "milli-volts"
    MAX-ACCESS  read-only
    STATUS      current
    DESCRIPTION "Cell4 Voltage - Cell 4 voltage in milli-volts
                 MQTT Payload Key: 'Cell4 Voltage'"
    ::= { batteryData 18 }

cell5Voltage OBJECT-TYPE
    SYNTAX      Integer32
    UNITS       "milli-volts"
    MAX-ACCESS  read-only
    STATUS      current
    DESCRIPTION "Cell5 Voltage - Cell 5 voltage in milli-volts
                 MQTT Payload Key: 'Cell5 Voltage'"
    ::= { batteryData 19 }

cell6Voltage OBJECT-TYPE
    SYNTAX      Integer32
    UNITS       "milli-volts"
    MAX-ACCESS  read-only
    STATUS      current
    DESCRIPTION "Cell6 Voltage - Cell 6 voltage in milli-volts
                 MQTT Payload Key: 'Cell6 Voltage'"
    ::= { batteryData 20 }

cell7Voltage OBJECT-TYPE
    SYNTAX      Integer32
    UNITS       "milli-volts"
    MAX-ACCESS  read-only
    STATUS      current
    DESCRIPTION "Cell7 Voltage - Cell 7 voltage in milli-volts
                 MQTT Payload Key: 'Cell7 Voltage'"
    ::= { batteryData 21 }

cell8Voltage OBJECT-TYPE
    SYNTAX      Integer32
    UNITS       "milli-volts"
    MAX-ACCESS  read-only
    STATUS      current
    DESCRIPTION "Cell8 Voltage - Cell 8 voltage in milli-volts
                 MQTT Payload Key: 'Cell8 Voltage'"
    ::= { batteryData 22 }

cell9Voltage OBJECT-TYPE
    SYNTAX      Integer32
    UNITS       "milli-volts"
    MAX-ACCESS  read-only
    STATUS      current
    DESCRIPTION "Cell9 Voltage - Cell 9 voltage in milli-volts
                 MQTT Payload Key: 'Cell9 Voltage'"
    ::= { batteryData 23 }

cell10Voltage OBJECT-TYPE
    SYNTAX      Integer32
    UNITS       "milli-volts"
    MAX-ACCESS  read-only
    STATUS      current
    DESCRIPTION "Cell10 Voltage - Cell 10 voltage in milli-volts
                 MQTT Payload Key: 'Cell10 Voltage'"
    ::= { batteryData 24 }

cell11Voltage OBJECT-TYPE
    SYNTAX      Integer32
    UNITS       "milli-volts"
    MAX-ACCESS  read-only
    STATUS      current
    DESCRIPTION "Cell11 Voltage - Cell 11 voltage in milli-volts
                 MQTT Payload Key: 'Cell11 Voltage'"
    ::= { batteryData 25 }

cell12Voltage OBJECT-TYPE
    SYNTAX      Integer32
    UNITS       "milli-volts"
    MAX-ACCESS  read-only
    STATUS      current
    DESCRIPTION "Cell12 Voltage - Cell 12 voltage in milli-volts
                 MQTT Payload Key: 'Cell12 Voltage'"
    ::= { batteryData 26 }

cell13Voltage OBJECT-TYPE
    SYNTAX      Integer32
    UNITS       "milli-volts"
    MAX-ACCESS  read-only
    STATUS      current
    DESCRIPTION "Cell13 Voltage - Cell 13 voltage in milli-volts
                 MQTT Payload Key: 'Cell13 Voltage'"
    ::= { batteryData 27 }

cell14Voltage OBJECT-TYPE
    SYNTAX      Integer32
    UNITS       "milli-volts"
    MAX-ACCESS  read-only
    STATUS      current
    DESCRIPTION "Cell14 Voltage - Cell 14 voltage in milli-volts
                 MQTT Payload Key: 'Cell14 Voltage'"
    ::= { batteryData 28 }

cell15Voltage OBJECT-TYPE
    SYNTAX      Integer32
    UNITS       "milli-volts"
    MAX-ACCESS  read-only
    STATUS      current
    DESCRIPTION "Cell15 Voltage - Cell 15 voltage in milli-volts
                 MQTT Payload Key: 'Cell15 Voltage'"
    ::= { batteryData 29 }

-- Cell Temperatures (30-33)
cellTemperature1 OBJECT-TYPE
    SYNTAX      Integer32
    UNITS       "centi-celsius"
    MAX-ACCESS  read-only
    STATUS      current
    DESCRIPTION "Cell temperature 1 - Cell temperature 1 in centi-celsius
                 MQTT Payload Key: 'Cell temperature 1'"
    ::= { batteryData 30 }

cellTemperature2 OBJECT-TYPE
    SYNTAX      Integer32
    UNITS       "centi-celsius"
    MAX-ACCESS  read-only
    STATUS      current
    DESCRIPTION "Cell temperature 2 - Cell temperature 2 in centi-celsius
                 MQTT Payload Key: 'Cell temperature 2'"
    ::= { batteryData 31 }

cellTemperature3 OBJECT-TYPE
    SYNTAX      Integer32
    UNITS       "centi-celsius"
    MAX-ACCESS  read-only
    STATUS      current
    DESCRIPTION "Cell temperature 3 - Cell temperature 3 in centi-celsius
                 MQTT Payload Key: 'Cell temperature 3'"
    ::= { batteryData 32 }

cellTemperature4 OBJECT-TYPE
    SYNTAX      Integer32
    UNITS       "centi-celsius"
    MAX-ACCESS  read-only
    STATUS      current
    DESCRIPTION "Cell temperature 4 - Cell temperature 4 in centi-celsius
                 MQTT Payload Key: 'Cell temperature 4'"
    ::= { batteryData 33 }

-- Environment Sensors (34-35)
environmentTemperature OBJECT-TYPE
    SYNTAX      Integer32
    UNITS       "centi-celsius"
    MAX-ACCESS  read-only
    STATUS      current
    DESCRIPTION "Environment Temperature - Environment temperature in centi-celsius
                 MQTT Payload Key: 'Environment Temperature'"
    ::= { batteryData 34 }

mosfetTemperature OBJECT-TYPE
    SYNTAX      Integer32
    UNITS       "centi-celsius"
    MAX-ACCESS  read-only
    STATUS      current
    DESCRIPTION "MOSFET temperature - MOSFET temperature in centi-celsius
                 MQTT Payload Key: 'MOSFET temperature'"
    ::= { batteryData 35 }

-- System Event (36) - Legacy single value
systemEvent OBJECT-TYPE
    SYNTAX      Integer32
    MAX-ACCESS  read-only
    STATUS      current
    DESCRIPTION "System Event - Raw system event register value (legacy - use individual System Event parameters below)
                 MQTT Payload Key: 'System Event' (raw UINT16 value)"
    ::= { batteryData 36 }

-- System Event Individual Parameters (37-46) - Matches payload 'System Event' dictionary
systemEventOverVoltageProtect OBJECT-TYPE
    SYNTAX      Integer32 (0..1)
    MAX-ACCESS  read-only
    STATUS      current
    DESCRIPTION "Over Voltage Protect - Over voltage protection status (0=normal, 1=protection active)
                 MQTT Payload Key: 'System Event' -> 'Over Voltage Protect'"
    ::= { batteryData 37 }

systemEventUnderVoltageProtect OBJECT-TYPE
    SYNTAX      Integer32 (0..1)
    MAX-ACCESS  read-only
    STATUS      current
    DESCRIPTION "Under Voltage Protect - Under voltage protection status (0=normal, 1=protection active)
                 MQTT Payload Key: 'System Event' -> 'Under Voltage Protect'"
    ::= { batteryData 38 }

systemEventChargeOverCurrentProtect OBJECT-TYPE
    SYNTAX      Integer32 (0..1)
    MAX-ACCESS  read-only
    STATUS      current
    DESCRIPTION "Charge over current Protect - Charge over current protection status (0=normal, 1=protection active)
                 MQTT Payload Key: 'System Event' -> 'Charge over current Protect'"
    ::= { batteryData 39 }

systemEventDischargeOverCurrentProtect OBJECT-TYPE
    SYNTAX      Integer32 (0..1)
    MAX-ACCESS  read-only
    STATUS      current
    DESCRIPTION "Discharge over current Protect - Discharge over current protection status (0=normal, 1=protection active)
                 MQTT Payload Key: 'System Event' -> 'Discharge over current Protect'"
    ::= { batteryData 40 }

systemEventShortReverseCircuitProtect OBJECT-TYPE
    SYNTAX      Integer32 (0..1)
    MAX-ACCESS  read-only
    STATUS      current
    DESCRIPTION "Short/Reverse circuit Protect - Short circuit protection status (0=normal, 1=protection active)
                 MQTT Payload Key: 'System Event' -> 'Short/Reverse circuit Protect'"
    ::= { batteryData 41 }

systemEventHighTemperaturePrtect OBJECT-TYPE
    SYNTAX      Integer32 (0..1)
    MAX-ACCESS  read-only
    STATUS      current
    DESCRIPTION "High temperature Prtect - High temperature protection status (0=normal, 1=protection active)
                 MQTT Payload Key: 'System Event' -> 'High temperature Prtect' (note: typo in original)"
    ::= { batteryData 42 }

systemEventSOCLowAlarm OBJECT-TYPE
    SYNTAX      Integer32 (0..1)
    MAX-ACCESS  read-only
    STATUS      current
    DESCRIPTION "SOC Low alarm - SOC low alarm status (0=normal, 1=alarm active)
                 MQTT Payload Key: 'System Event' -> 'SOC Low alarm'"
    ::= { batteryData 43 }

systemEventDischarging OBJECT-TYPE
    SYNTAX      Integer32 (0..1)
    MAX-ACCESS  read-only
    STATUS      current
    DESCRIPTION "Discharging - Discharging status (0=not discharging, 1=discharging)
                 MQTT Payload Key: 'System Event' -> 'Discharging'"
    ::= { batteryData 44 }

systemEventChargeing OBJECT-TYPE
    SYNTAX      Integer32 (0..1)
    MAX-ACCESS  read-only
    STATUS      current
    DESCRIPTION "Chargeing - Charging status (0=not charging, 1=charging)
                 MQTT Payload Key: 'System Event' -> 'Chargeing' (note: typo in original)"
    ::= { batteryData 45 }

systemEventChargeOnline OBJECT-TYPE
    SYNTAX      Integer32 (0..1)
    MAX-ACCESS  read-only
    STATUS      current
    DESCRIPTION "Charge Online - Charge online status (0=offline, 1=online)
                 MQTT Payload Key: 'System Event' -> 'Charge Online'"
    ::= { batteryData 46 }

-- Trap Definitions - Using new naming
batteryLowVoltage NOTIFICATION-TYPE
    OBJECTS { packVoltage, soc, deviceName, siteName }
    STATUS  current
    DESCRIPTION "Battery pack voltage below threshold alarm"
    ::= { Traps 1 }

batteryHighVoltage NOTIFICATION-TYPE
    OBJECTS { packVoltage, soc, deviceName, siteName }
    STATUS  current
    DESCRIPTION "Battery pack voltage above threshold alarm"
    ::= { Traps 2 }

batteryLowSOC NOTIFICATION-TYPE
    OBJECTS { soc, packVoltage, deviceName, siteName }
    STATUS  current
    DESCRIPTION "Battery State of Charge below threshold alarm"
    ::= { Traps 3 }

batteryHighTemp NOTIFICATION-TYPE
    OBJECTS { maxCellTemperature, packVoltage, soc, deviceName, siteName }
    STATUS  current
    DESCRIPTION "Battery temperature above threshold alarm"
    ::= { Traps 4 }

-- BMS Protection Traps
batteryOverVoltageProtect NOTIFICATION-TYPE
    OBJECTS { systemEventOverVoltageProtect, packVoltage, deviceName, siteName }
    STATUS  current
    DESCRIPTION "BMS Over Voltage Protection activated"
    ::= { TrapProtect 1 }

batteryUnderVoltageProtect NOTIFICATION-TYPE
    OBJECTS { systemEventUnderVoltageProtect, packVoltage, deviceName, siteName }
    STATUS  current
    DESCRIPTION "BMS Under Voltage Protection activated"
    ::= { TrapProtect 2 }

batteryChargeOCProtect NOTIFICATION-TYPE
    OBJECTS { systemEventChargeOverCurrentProtect, current, deviceName, siteName }
    STATUS  current
    DESCRIPTION "BMS Charge Over Current Protection activated"
    ::= { TrapProtect 3 }

batteryDischargeOCProtect NOTIFICATION-TYPE
    OBJECTS { systemEventDischargeOverCurrentProtect, current, deviceName, siteName }
    STATUS  current
    DESCRIPTION "BMS Discharge Over Current Protection activated"
    ::= { TrapProtect 4 }

batteryShortCircuitProtect NOTIFICATION-TYPE
    OBJECTS { systemEventShortReverseCircuitProtect, packVoltage, deviceName, siteName }
    STATUS  current
    DESCRIPTION "BMS Short Circuit Protection activated"
    ::= { TrapProtect 5 }

batteryHighTempProtect NOTIFICATION-TYPE
    OBJECTS { systemEventHighTemperaturePrtect, maxCellTemperature, deviceName, siteName }
    STATUS  current
    DESCRIPTION "BMS High Temperature Protection activated"
    ::= { TrapProtect 6 }

-- BMS Status Traps
batterySOCLowAlarm NOTIFICATION-TYPE
    OBJECTS { systemEventSOCLowAlarm, soc, deviceName, siteName }
    STATUS  current
    DESCRIPTION "BMS SOC Low Alarm"
    ::= { TrapStatus 1 }

batteryDischargingStatus NOTIFICATION-TYPE
    OBJECTS { systemEventDischarging, current, deviceName, siteName }
    STATUS  current
    DESCRIPTION "Battery Discharging Status"
    ::= { TrapStatus 2 }

batteryChargingStatus NOTIFICATION-TYPE
    OBJECTS { systemEventChargeing, current, deviceName, siteName }
    STATUS  current
    DESCRIPTION "Battery Charging Status"
    ::= { TrapStatus 3 }

batteryChargeOnlineStatus NOTIFICATION-TYPE
    OBJECTS { systemEventChargeOnline, packVoltage, deviceName, siteName }
    STATUS  current
    DESCRIPTION "Battery Charge Online Status"
    ::= { TrapStatus 4 }

END
